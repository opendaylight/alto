module simple-alto-adsal-impl {
    yang-version 1;
    namespace "urn:opendaylight:alto:simple-impl";

    prefix alto-simple;

    import config {
        prefix config;
        revision-date 2013-04-05;
    }

    import opendaylight-md-sal-binding {
        prefix mdsal;
        revision-date 2013-10-28;
    }

    description
        "This module contains the base YANG definition for adsal-based northbound services";

    revision "2015-05-12" {
        description "Initial revision";
    }

    identity simple-alto-adsal-impl {
        base config:module-type;

        config:java-name-prefix SimpleAltoImpl;
    }

    augment "/config:modules/config:module/config:configuration" {
        case simple-alto-adsal-impl {
            when "/config:modules/config:module/config:type = 'simple-alto-adsal-impl'";

            container rpc-registry {
                uses config:service-ref {
                    refine type {
                        mandatory true;
                        config:required-identity mdsal:binding-rpc-registry;
                    }
                }
            }

            container data-broker {
                uses config:service-ref {
                    refine type {
                        mandatory true;
                        config:required-identity mdsal:binding-async-data-broker;
                    }
                }
            }
        }
    }
}
