module alto-manual-maps {
    yang-version 1;
    namespace "urn:opendaylight:params:xml:ns:yang:alto-manual-maps";
    prefix "alto-manual-maps";

    revision "2015-01-05" {
        description "Initial revision of alto-manual-maps model";
    }
}
