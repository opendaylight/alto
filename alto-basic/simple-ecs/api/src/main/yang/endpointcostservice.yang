module endpointcostservice {
    yang-version 1;
    namespace "urn:opendaylight:params:xml:ns:yang:endpointcostservice";
    prefix "endpointcostservice";

    revision "2015-01-05" {
        description "Initial revision of endpointcostservice model";
    }
}
