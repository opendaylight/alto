module alto-simple-ird-impl {
    yang-version 1;
    namespace "urn:alto:simple:ird:impl";
    prefix "alto-simple-ird-impl";

    import alto-northbound { prefix alto-northbound; revision-date 2015-10-21; }
    import config { prefix config; revision-date 2013-04-05; }
    import opendaylight-md-sal-binding { prefix md-sal-binding; revision-date 2013-10-28;}

    description
        "Service definition for alto-simple-ird project";

    revision "2015-10-21" {
        description
            "Initial revision";
    }

    identity alto-simple-ird {
        base config:module-type;
        config:java-name-prefix AltoSimpleIrd;
    }

    augment "/config:modules/config:module/config:configuration" {
        case alto-simple-ird {
            when "/config:modules/config:module/config:type = 'alto-simple-ird'";
            container broker {
                uses config:service-ref {
                    refine type {
                        mandatory true;
                        config:required-identity md-sal-binding:binding-broker-osgi-registry;
                    }
                }
            }

            container alto-northbound-router {
                uses config:service-ref {
                    refine type {
                        mandatory true;
                        config:required-identity alto-northbound:alto-northbound-router;
                    }
                }
            }
        }
    }
}
