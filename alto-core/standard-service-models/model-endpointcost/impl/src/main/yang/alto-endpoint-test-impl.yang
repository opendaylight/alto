module alto-endpointcost-test-impl {
    yang-version 1;
    namespace "urn:alto:service:model:test:endpointcost";
    prefix "alto-model-endpointcost-test-impl";

    import config { prefix config; revision-date 2013-04-05; }
    import opendaylight-md-sal-binding { prefix md-sal-binding; revision-date 2013-10-28;}

    description
        "Service definition for endpointcost project";

    revision "2015-10-21" {
        description
            "Initial revision";
    }

    identity alto-model-endpointcost-test {
        base config:module-type;
        config:java-name-prefix AltoEndpointCost;
    }

    augment "/config:modules/config:module/config:configuration" {
        case alto-model-endpointcost-test-impl {
            when "/config:modules/config:module/config:type = 'alto-model-endpointcost-test'";
            container broker {
                uses config:service-ref {
                    refine type {
                        mandatory true;
                        config:required-identity md-sal-binding:binding-broker-osgi-registry;
                    }
                }
            }
        }
    }
}
