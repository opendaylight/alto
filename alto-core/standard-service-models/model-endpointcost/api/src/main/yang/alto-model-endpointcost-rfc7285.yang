module alto-model-endpointcost-rfc7285 {
    yang-version 1;

    namespace "urn:alto:service:model:endpointcost:rfc7285";

    prefix "alto-model-endpointcost-rfc7285";

    import "alto-model-endpointcost" {
        prefix "alto-ecs";
    }

    import "ietf-inet-types" {
        prefix "ietf-inet";
    }

    import yang-ext {
        prefix ext;
    }

    organization "Yale University";

    contact "alto-dev@lists.opendaylight.org";

    revision "2015-10-21" {
        description "Initial revision of alto endpointcost";
    }

    grouping "typed-address-data" {
        choice "address" {
        }
    }

    grouping "endpoint-filter-data" {
        container "endpoint-filter" {
            list "source" {
                uses "typed-address-data";
            }

            list "destination" {
                uses "typed-address-data";
            }
        }
    }

    augment "/alto-ecs:query/alto-ecs:input/alto-ecs:request"
            + "/alto-ecs:endpointcost-request"
            + "/alto-ecs:endpointcost-params/alto-ecs:filter" {
        ext:augment-identifier "rfc7285-endpoint-filter";

        case "endpoint-filter-data" {
            uses "endpoint-filter-data";
        }
    }

    identity "endpointcost-response-type-endpointcostmap" {
        base "alto-ecs:endpointcost-response-type-base";
    }

    grouping "endpointcostmap-response-data" {
        container "endpoint-cost-map" {
            list "endpoint-cost" {
                container "source" {
                    uses "typed-address-data";
                }

                container "destination" {
                    uses "typed-address-data";
                }

                choice "cost" {
                }
            }
        }
    }

    augment "/alto-ecs:query/alto-ecs:output/alto-ecs:response"
            + "/alto-ecs:endpointcost-response"
            + "/alto-ecs:endpointcost-data" {
        ext:augment-identifier "rfc7285-endpoint-cost-map";

        case "endpoint-costmap-data" {
            uses "endpointcostmap-response-data";
        }
    }

    grouping "ipv4-address-data" {
        leaf "ipv4" {
            type ietf-inet:ipv4-address;
        }
    }

    grouping "ipv6-address-data" {
        leaf "ipv6" {
            type ietf-inet:ipv6-address;
        }
    }

    augment "/alto-ecs:query/alto-ecs:input/alto-ecs:request"
            + "/alto-ecs:endpointcost-request"
            + "/alto-ecs:endpointcost-params"
            + "/alto-ecs:filter/endpoint-filter-data"
            + "/endpoint-filter/source/address" {
        ext:augment-identifier "rfc7285-endpoint-filter-source";

        case ipv4 {
            uses "ipv4-address-data";
        }

        case ipv6 {
            uses "ipv6-address-data";
        }
    }

    augment "/alto-ecs:query/alto-ecs:input/alto-ecs:request"
            + "/alto-ecs:endpointcost-request"
            + "/alto-ecs:endpointcost-params"
            + "/alto-ecs:filter/endpoint-filter-data"
            + "/endpoint-filter/destination/address" {
        ext:augment-identifier "rfc7285-endpoint-filter-destination";
        case ipv4 {
            uses "ipv4-address-data";
        }

        case ipv6 {
            uses "ipv6-address-data";
        }
    }

    augment "/alto-ecs:query/alto-ecs:output/alto-ecs:response"
            + "/alto-ecs:endpointcost-response"
            + "/alto-ecs:endpointcost-data"
            + "/endpoint-costmap-data/endpoint-cost-map/endpoint-cost/source/address" {
        ext:augment-identifier "rfc7285-endpoint-costmap-source";

        case ipv4 {
            uses "ipv4-address-data";
        }

        case ipv6 {
            uses "ipv6-address-data";
        }
    }


    augment "/alto-ecs:query/alto-ecs:output/alto-ecs:response"
            + "/alto-ecs:endpointcost-response"
            + "/alto-ecs:endpointcost-data"
            + "/endpoint-costmap-data/endpoint-cost-map/endpoint-cost/destination/address" {
        ext:augment-identifier "rfc7285-endpoint-costmap-destination";

        case ipv4 {
            uses "ipv4-address-data";
        }

        case ipv6 {
            uses "ipv6-address-data";
        }
    }

    augment "/alto-ecs:query/alto-ecs:output/alto-ecs:response"
            + "/alto-ecs:endpointcost-response"
            + "/alto-ecs:endpointcost-data"
            + "/endpoint-costmap-data/endpoint-cost-map/endpoint-cost/cost" {
        ext:augment-identifier "rfc7825-endpoint-costmap-cost";

        case numerical {
            leaf "cost" {
                type decimal64 {
                    fraction-digits 4;
                }
            }
        }

       case ordinal {
            leaf "cost" {
                type int32;
            }
        }
    }
}
