module alto-model-endpointcost {
    yang-version 1;

    namespace "urn:alto:service:model:endpointcost";

    prefix "alto-model-endpointcost";

    import "alto-basic-types" {
        prefix "alto-types";
    }

    import "alto-resourcepool" {
        prefix "alto-resourcepool";
    }

    import "alto-model-base" {
        prefix "base";
    }

    import "alto-model-networkmap" {
        prefix "networkmap";
    }

    import "ietf-inet-types" {
        prefix "ietf-inet";
    }

    import "yang-ext" {
        prefix "yang-ext";
    }

    organization "Yale University";

    contact "alto-dev@lists.opendaylight.org";

    revision "2015-10-21" {
        description "Initial revision of alto endpointcost";
    }

    identity "resource-type-endpointcost" {
        base "alto-resourcepool:resource-type";
        description
            "The resource type for endpoint cost service";
    }

    grouping "cost-type-container" {
        container "cost-type" {
            uses "alto-types:cost-type-data";
        }
    }

    grouping "endpointcost-request-data" {
        container "endpointcost-params" {
            uses "cost-type-container";

            leaf-list "constraints" {
                type string;
            }

            choice "filter" {
            }
        }
    }

    identity "endpointcost-response-type-base" {
        description
            "Base identity for endpoint cost response";
    }

    grouping "endpointcost-response-data" {
        choice "endpointcost-data" {
        }
    }

    grouping "alto-request-endpointcost" {
        uses "base:alto-request-base" {
            augment "request" {
                case "endpointcost-request" {
                    uses "endpointcost-request-data";
                }
            }
        }
    }

    grouping "alto-response-endpointcost" {
        uses "base:alto-response-error" {
            augment "response" {
                case "endpointcost-response" {
                    uses "endpointcost-response-data";
                }
            }
        }
    }

    rpc query {
        input {
            uses "alto-request-endpointcost";
        }

        output {
            uses "alto-response-endpointcost";
        }
    }

    augment "/alto-resourcepool:context"
            + "/alto-resourcepool:resource"
            + "/alto-resourcepool:capabilities" {
        yang-ext:augment-identifier "capabilities-cost-type";

        list "cost-type" {
            uses "alto-types:cost-type-data";

            leaf "description" {
                type string;
            }
        }

        leaf "constraint-support" {
            type boolean;
        }
    }
}
