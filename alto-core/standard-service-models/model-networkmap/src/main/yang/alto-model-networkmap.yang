module alto-model-networkmap {

    yang-version 1;

    namespace "urn:opendaylight:alto:service:model:networkmap";

    prefix "alto-model-networkmap";

    import "alto-basic-types" {
        prefix "alto-types";
    }

    import "alto-resourcepool" {
        prefix "alto-resourcepool";
    }

    import "alto-model-base" {
        prefix "base";
    }

    organization "Yale University";

    contact "alto-dev@lists.opendaylight.org";

    revision "2015-10-21" {
        description "Initial revision of alto networkmap";
    }

    identity "resource-type-networkmap" {
        base "alto-resourcepool:resource-type";
        description
            "The resource type for network map";
    }

    identity "resource-type-filtered-networkmap" {
        base "alto-resourcepool:resource-type";
        description
            "The resource type for filtered network map";
    }

    identity "property-type-base" {
        description
            "Base type for PID properties";
    }

    identity "address-type-base" {
        base "property-type-base";
        description
            "Base type for address type";
    }

    grouping "networkmap-request-data" {
        container "networkmap-filter" {
            leaf-list "pid" {
                type "alto-types:pid-name";
            }

            leaf-list "address-type" {
                type identityref {
                    base "address-type-base";
                }
            }
        }
    }

    grouping "networkmap-response-data" {
        container "network-map" {
            list "partition" {
                key "pid";

                leaf "pid" {
                    type "alto-types:pid-name";
                }
            }
        }
    }

    grouping "alto-request-networkmap" {
        uses "base:alto-request-base" {
            augment "request" {
                case "networkmap-request" {
                    uses "networkmap-request-data";
                }
            }
        }
    }

    grouping "alto-response-networkmap" {
        uses "base:alto-response-error" {
            augment "response" {
                case "networkmap-response" {
                    uses "networkmap-response-data";
                }
            }
        }
    }

    rpc query {
        input {
            uses "alto-request-networkmap";
        }

        output {
            uses "alto-response-networkmap";
        }
    }

    identity "address-type-ipv4" {
        base "address-type-base";
        description
            "Address type for IPv4";
    }

    identity "address-type-ipv6" {
        base "address-type-base";
        description
            "Address type for IPv6";
    }

}
