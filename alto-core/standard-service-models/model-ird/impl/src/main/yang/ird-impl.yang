module alto-ird-test-impl {
    yang-version 1;
    namespace "urn:alto:service:model:test:ird";
    prefix "alto-model-ird-test-impl";

    import config { prefix config; revision-date 2013-04-05; }
    import opendaylight-md-sal-binding { prefix md-sal-binding; revision-date 2013-10-28;}

    description
        "Service definition for ird project";

    revision "2015-10-21" {
        description
            "Initial revision";
    }

    identity alto-model-ird-test {
        base config:module-type;
        config:java-name-prefix AltoIrd;
    }

    augment "/config:modules/config:module/config:configuration" {
        case alto-model-ird-test-impl {
            when "/config:modules/config:module/config:type = 'alto-model-ird-test'";
            container broker {
                uses config:service-ref {
                    refine type {
                        mandatory true;
                        config:required-identity md-sal-binding:binding-broker-osgi-registry;
                    }
                }
            }
        }
    }
}
