module alto-nbr-endpointcost {
    yang-version 1;

    namespace "urn:alto:northbound:route:endpointcost";

    prefix "alto-nbr-endpointcost";

    import ietf-inet-types { prefix ietf-inet; revision-date 2013-07-15; }
    import alto-model-endpointcost { prefix endpointcost-model; revision-date 2015-10-21; }

    organization "Yale University";

    contact "alto-dev@lists.opendaylight.org";

    revision "2015-10-21" {
        description "Initial revision of alto-northbound model";
    }

    container "records" {
        list "record" {
            key "path";

            leaf "path" {
                type ietf-inet:uri;
            }

            leaf "resource-iid" {
                type instance-identifier;
            }


        }
    }

}
