module alto-northbound-route-endpointproperty-impl {
    yang-version 1;
    namespace "urn:alto:northbound:route:endpointproperty:impl";
    prefix "alto-northbound-router-endpointproperty-impl";

    import alto-northbound { prefix alto-northbound; revision-date 2015-10-21; }
    import config { prefix config; revision-date 2013-04-05; }
    import opendaylight-md-sal-binding { prefix md-sal-binding; revision-date 2013-10-28;}

    description
        "Service definition for northbound project";

    revision "2015-10-21" {
        description
            "Initial revision";
    }

    identity alto-northbound-route-endpointproperty-impl {
        base config:module-type;
        config:java-name-prefix AltoNorthboundRouteEndpointproperty;
    }

    augment "/config:modules/config:module/config:configuration" {
        case alto-northbound-route-endpointproperty {
            when "/config:modules/config:module/config:type = 'alto-northbound-route-endpointproperty-impl'";
            container broker {
                uses config:service-ref {
                    refine type {
                        mandatory true;
                        config:required-identity md-sal-binding:binding-broker-osgi-registry;
                    }
                }
            }

            container alto-northbound-router {
                uses config:service-ref {
                    refine type {
                        mandatory true;
                        config:required-identity alto-northbound:alto-northbound-router;
                    }
                }
            }
        }

    }
}
