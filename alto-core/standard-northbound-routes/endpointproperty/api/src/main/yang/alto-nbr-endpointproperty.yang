module alto-nbr-endpointproperty {
    yang-version 1;
    namespace "urn:alto:northbound:route:endpointproperty";
    prefix "alto-nbr-endpointproperty";

    import ietf-inet-types { prefix ietf-inet; revision-date 2013-07-15; }

    organization "Yale University";

    contact "alto-dev@lists.opendaylight.org";

    revision "2015-10-21" {
        description "Initial revision of endpointproperty model";
    }

    container "records" {
        list "record" {
            key "path";

            leaf "path" {
                type ietf-inet:uri;
            }

            leaf "resource-iid" {
                type instance-identifier;
            }
        }
    }
}
