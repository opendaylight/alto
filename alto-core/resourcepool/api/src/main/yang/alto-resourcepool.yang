module alto-resourcepool {
    yang-version 1;

    namespace "urn:alto:resourcepool";

    prefix "alto-resourcepool";

    import "alto-basic-types" {
        prefix "alto-types";
    }

    import "yang-ext" {
        prefix "yang-ext";
    }

    import "ietf-yang-types" {
        prefix "ietf-types";
    }

    import "ietf-inet-types" {
        prefix "ietf-inet";
    }

    organization "Yale University";

    contact "alto-dev@lists.opendaylight.org";

    revision "2015-09-21" {
        description "Initial revision of alto resourcepool";
    }

    identity "service-context" {
        description
            "The context identifier for a certain ALTO service";
    }

    identity "resource-type" {
        description
            "The basic type identity for ALTO resourcepool";
    }

    list "context" {
        config false;

        key "context-id";

        leaf "context-id" {
            type ietf-types:uuid;
            default "00000000-0000-0000-0000-000000000000";
        }

        list "resource" {
            key "resource-id";

            leaf "resource-id" {
                type alto-types:resource-id;
            }

            leaf "type" {
                type identityref {
                    base "resource-type";
                }
            }

            container "capabilities" {
            }

            leaf "default-tag" {
                type leafref {
                    path "../context-tag/tag";
                }
            }

            list "context-tag" {
                key "tag";

                leaf "tag" {
                    type alto-types:tag;
                }

                yang-ext:context-instance "service-context";

                leaf-list "dependency" {
                    description
                        "Should point to a ../../../resource/context-tag instance (in the same context)";
                    type instance-identifier {
                        require-instance true;
                    }
                }
            }
        }
    }
}
