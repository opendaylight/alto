module alto-resourcepool-impl {
    yang-version 1;

    namespace "urn:alto:resourcepool:impl";

    prefix "alto-resourcepool-impl";

    import "config" {
        prefix "config";
        revision-date 2013-04-05;
    }

    import opendaylight-md-sal-binding {
        prefix "md-sal-binding";
        revision-date 2013-10-28;
    }

    description
        "Service definition for resources project";

    revision "2015-09-21" {
        description
            "Initial revision";
    }

    identity "alto-resourcepool-provider" {
        base config:module-type;
        config:java-name-prefix AltoResourcepool;
    }

    augment "/config:modules/config:module/config:configuration" {
        case alto-resourcepool {
            when "/config:modules/config:module/config:type = 'alto-resourcepool-provider'";

            container broker {
                uses config:service-ref {
                    refine type {
                        mandatory true;
                        config:required-identity md-sal-binding:binding-broker-osgi-registry;
                    }
                }
            }
        }
    }
}
