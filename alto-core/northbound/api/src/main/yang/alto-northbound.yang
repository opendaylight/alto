module alto-northbound {
    yang-version 1;

    namespace "urn:alto:northbound";

    prefix "alto-northbound";

    import config { prefix config; revision-date 2013-04-05; }

    organization "Yale University";

    contact "alto-dev@lists.opendaylight.org";

    revision "2015-10-21" {
        description "Initial revision of alto-northbound model";
    }

    identity alto-northbound-router {
        base "config:service-type";
        config:java-class "org.opendaylight.alto.core.northbound.api.AltoNorthboundRouter";
    }

    identity alto-northbound-route {
        base "config:service-type";
        config:java-class "org.opendaylight.alto.core.northbound.api.AltoNorthboundRoute";
    }

}
