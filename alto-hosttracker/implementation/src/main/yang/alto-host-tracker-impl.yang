module alto-host-tracker-impl {

  yang-version 1;
  namespace "urn:opendaylight:alto:alto-host-tracker-impl";
  prefix "alto-host-tracker-impl";

  import config { prefix config; revision-date 2013-04-05; }
  import opendaylight-md-sal-binding { prefix mdsal; revision-date 2013-10-28; }

  description
    "This module contains the base YANG definitions for
    alto-host-tracker-impl implementation.";

  revision 2014-05-28 {
    description "Initial module draft.";
  }

  // This is the definition of the service implementation as a module identity.
  identity alto-host-tracker-impl {
    base config:module-type;

    // Specifies the prefix for generated java classes.
    config:java-name-prefix AltoHostTracker;
  }

  // Augments the 'configuration' choice node under modules/module.
  // We consume the three main services, RPCs, DataStore, and Notifications
  augment "/config:modules/config:module/config:configuration" {
    case alto-host-tracker-impl {
      when "/config:modules/config:module/config:type = 'alto-host-tracker-impl'";

      leaf topology-id {
        type string;
      }
      container data-broker {
        uses config:service-ref {
          refine type {
            mandatory false;
            config:required-identity mdsal:binding-async-data-broker;
          }
        }
      }
    }
  }
}
