module alto-hosttracker-cost-service {
    namespace "urn:opendaylight:alto:hosttracker";
    prefix alto-host-track-cost;

    import ietf-yang-types {prefix yang;}
    import alto-service {prefix alto-restconf;}
    import alto-service-types {prefix alto;}

    revision 2015-04-16 {
        description
            "augment cost in alto-service-types";
    }

    grouping cost {
        description "cost set in hosttracker";
        leaf cost-value {
            type int32;
        }
    }

    augment "/alto-restconf:resources/alto-restconf:cost-maps/alto-restconf:cost-map/alto-restconf:map/alto-restconf:dst-costs" {
        when "/alto-restconf:resources/alto-restconf:cost-maps/alto-restconf:cost-map/alto-restconf:meta/alto-restconf:cost-type/alto-restconf:cost-mode = 'numerical'";
        leaf cost-in-hosttracker {
            type int32;
        }
    }
}
