module alto-service {
  //alto-service-restconf

  yang-version 1;

  namespace "urn:opendaylight:alto";
  // TODO: replace with IANA namespace when assigned

  prefix "alto-restconf";

  import alto-service-types {
    prefix alto;
  }

  organization "ALTO WG";
  contact "alto@ietf.org";

  description
    "This module defines a data model for the ALTO services
     using restconf. Note this is not interop with RFC7285.";

  revision 2015-04-04 {
    description "Fix IRD";
  }

  revision 2014-11-19 {
    description "Initial version for ODL.";
  }

  grouping network-map {
    leaf resource-id {
      type alto:resource-id;
        mandatory true;
      }
    leaf tag {
      type alto:tag-string;
        mandatory true;
      }
    list map {
      key "pid";
      leaf pid {
        type alto:pid-name;
      }
      uses alto:endpoint-address-group;
    }
  }

  grouping cost-map {
    leaf resource-id {
      type alto:resource-id;
      mandatory true;
    }
    leaf tag {
      type alto:tag-string;
      mandatory true;
    }
    container meta {
      must "current()";
      uses alto:cost-map-meta;
    }
    list map {
      leaf src {
        type alto:pid-name;
      }
      key "src";
      list dst-costs {
        leaf dst {
          type alto:pid-name;
        }
        key "dst";
        //uses alto:alto-cost;
      }
    }
  }

  /************************************
   * Data Instances                   *
   ************************************/

  container resources {
    //presence "Indicates that the alto service is available.";

    container IRD {
      uses alto:IRD;
    }

    container network-maps {
      list network-map {
        key "resource-id";
        uses network-map;
      }
    }

    container cost-maps {
      list cost-map {
        key "resource-id";
        uses cost-map;
      }
    }

    container endpoint-property-map {
      uses alto:endpoint-property-map;
    }
  }

  /************************************
   * RPCs                             *
   ************************************/

  rpc filtered-network-map-service {
    input {
      leaf resource-id {
        mandatory true;
        type alto:resource-id;
      }
      leaf-list pids {
        must "current()";
        type alto:pid-name;
      }
      leaf-list address-types {
        type alto:endpoint-address-type;
      }
    }
    output {
      container filtered-network-map-service {
        uses network-map;
      }
    }
  }

  rpc filtered-cost-map-service {
    input {
      leaf resource-id {
        mandatory true;
        type alto:resource-id;
      }
      container cost-type {
        must "current()";
        uses alto:cost-type;
      }
      leaf-list constraints {
        type alto:constraint;
      }
      container pids {
        leaf-list srcs {
          type alto:pid-name;
        }
        leaf-list dsts {
          type alto:pid-name;
        }
      }
    }
    output {
      container filtered-cost-map-service {
        uses cost-map;
      }
    }
  }

  rpc endpoint-cost-service {
    input {
      container cost-type {
        must "current()";
        uses alto:cost-type;
      }
      leaf-list constraints {
        type alto:constraint;
      }
      container endpoints {
        must "current()";
        leaf-list srcs {
          type alto:typed-endpoint-address;
        }
        leaf-list dsts {
          type alto:typed-endpoint-address;
        }
      }
    }
    output {
      container endpoint-cost-service {
        container meta {
          container cost-type {
            uses alto:cost-type;
          }
        }
        list endpoint-cost-map {
          leaf src {
            type alto:typed-endpoint-address;
          }
          key "src";
          list dst-costs {
            leaf dst {
              type alto:typed-endpoint-address;
            }
            key "dst";
            //uses alto:alto-cost;
          }
        }
      }
    }
  }

}
