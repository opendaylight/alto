module alto-service-did {
  yang-version 1;

  namespace "urn:opendaylight:alto-service-did";
  // TODO: replace with IANA namespace when assigned

  prefix "as-did";

  import alto-service-types {
    prefix alto;
  }

  organization "ALTO WG";
  contact "alto@ietf.org";

  description
    "This module defines the data instance descriptions (DID) of a
     semantically equivalent data model for the ALTO services
     defined in RFC7285.";

  revision 2014-11-01 {
    description "Inherit from alto-service-rpc and types.";
  }

  revision 2014-10-24 {
    description "Initial version.";
  }

  /******************************************
    Groupings for ALTO information resource
  *******************************************/

  grouping network-map-data {
    list map {
      key "pid";
      leaf pid {
        type alto:pid-name;
      }
      uses alto:endpoint-address-group;
    }
  }

  /* Network Map Grouping */
  grouping network-map {
    leaf resource-id {
      type alto:resource-id;
      mandatory true;
    }
    leaf tag {
      type alto:tag-string;
      mandatory true;
    }
    uses network-map-data;
  }

  grouping cost-map-data {
    list map {
      leaf src {
        type alto:pid-name;
      }
      key "src";
      list dst-costs {
        leaf dst {
          type alto:pid-name;
        }
        key "dst";
        uses alto:alto-cost;
      }
    }
  }

  /* Cost Map Grouping */
  grouping cost-map {
    leaf resource-id {
      type alto:resource-id;
      mandatory true;
    }
    leaf tag {
      type alto:tag-string;
      mandatory true;
    }
    container meta {
      must "current()";
      uses alto:cost-map-meta;
    }
    uses cost-map-data;
  }

  grouping alto-resources {
    container IRD {
      config false;
      uses alto:IRD;
    }

    container network-maps {
      config false;
      list network-map {
        key "resource-id";
        uses network-map;
      }
    }

    container cost-maps {
      config false;
      list cost-map {
        key "resource-id";
        uses cost-map;
      }
    }

    container endpoint-property-map {
      config false;
      uses alto:endpoint-property-map;
    }
  }

  /****************************************************
     DATA INSTANCES of all ALTO information resources

     unfiltered network-maps, unfiltered cost-maps are all instances
     of resources. IRD is also modeled as data.

     The design uses augment as the basic approach to implement
     inheritance.
   ****************************************************/
/*
  container resources {
    config false;
    uses alto-resources;
  }
*/
}
