module alto-impl {
    yang-version 1;
    namespace "urn:opendaylight:params:xml:ns:yang:alto:impl";
    prefix "alto-impl";

    import config { prefix config; revision-date 2013-04-05; }
    import opendaylight-md-sal-binding { prefix md-sal-binding; revision-date 2013-10-28;}

    description
        "Service definition for alto project";

    revision "2014-12-10" {
        description
            "Initial revision";
    }

    identity alto-impl {
        base config:module-type;
        config:java-name-prefix AltoImpl;
    }

    augment "/config:modules/config:module/config:configuration" {
        case alto-impl {
            when "/config:modules/config:module/config:type = 'alto-impl'";
            container broker {
                uses config:service-ref {
                    refine type {
                        mandatory true;
                        config:required-identity md-sal-binding:binding-broker-osgi-registry;
                    }
                }
            }
        }
    }
}
